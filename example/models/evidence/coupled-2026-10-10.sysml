// Generated by tools.boat_analysis.evidence.model; edit source evidence only through a new recorded run.
package BlueDogRecordedSizing {
    private import ScalarValues::*;
    doc /* Exploratory run at source revision 5ed1a1a78bf2099b71baf455b1a4a47714bc1736.
     * Evidence: evidence/runs/2026-10-10-coupled/manifest.json.
     * This projection preserves the recorded run, not a rerun of the current model. */
    part candidate : MarineDesign::Design {
        attribute :>> length_m = 1.807443825922969;
        attribute :>> beam_m = 0.65429468322854833;
        attribute :>> bottom_depth_m = 0.055209869713076773;
        attribute :>> deck_height_m = 0.11736969654075137;
        attribute :>> sail_m2 = 1.2797103004630528;
        attribute :>> sail_AR = 3.9980406361782688;
        attribute :>> camber_scale = 1.0887307817804102;
        attribute :>> wing_thickness_scale = 2;
        attribute :>> mast_fraction = 0.50514999095613922;
        attribute :>> mast_x_fraction = -0.014819264906112906;
        attribute :>> keel_m2 = 0.15414394281400351;
        attribute :>> keel_span_m = 0.73366559778329299;
        attribute :>> rudder_m2 = 0.0065043362556077358;
        attribute :>> rudder_span_m = 0.094949450801005628;
        attribute :>> rudder_arm_fraction = 0.65000000000000002;
        attribute :>> ballast_kg = 11.419036101104718;
        attribute :>> battery_Wh = 202.04795208249863;
        attribute :>> panel_m2 = 0.22484226038869715;
        attribute :>> wing_torque_Nm = 1.47400775527911;
        attribute :>> rudder_torque_Nm = 0.050000000000000003;
        attribute :>> hull_glass_kg_m2 = 0.43732697228578921;
        attribute :>> wing_glass_kg_m2 = 0.41837175232357449;
        attribute :>> keel_glass_kg_m2 = 5.177595530680474;
        attribute :>> rudder_glass_kg_m2 = 1.2624198475095523;
        attribute :>> hull_rib_pitch_m = 0.02168468045316662;
        attribute :>> foil_rib_pitch_m = 0.22996551066596616;
        attribute :>> battery_x_fraction = -0.3492051574654379;
        attribute :>> battery_z_fraction = 0.050000000000000003;
        attribute :>> hull_fullness_exponent = 2;
    }
    part nominal : BlueDogSizingEvidence::Scenario {
        attribute :>> label = "nominal";
        attribute :>> numericallyBalanced = true;
        attribute :>> missingPitchRoots = 0;
        attribute :>> pitchUnstableSamples = 86;
        attribute :>> diagnosticControlCases = 0;
        attribute :>> easterlyHours = 67.95286846237228;
        attribute :>> westerlyHours = 54.899322200049156;
        attribute :>> massKg = 31.447719266406427;
        attribute :>> evidenceAccepted = false;
        attribute :>> operatingMargins = (-2.7542028657734363e-09);
        attribute :>> structuralMargins = (0.94543513836936344,0.66837739039140598,0.793811093735875,0.48102813749816431,0.89146433697702698,8.0834283378017346e-08,-6.0907544834343241e-06,0.00093615008183722814,0.75999985862045649,-8.8362227712579511e-07,0.30885760961849151,0.69084260925563856,-1.5261190828841364e-06,0.90378668948452445,1.3527871062958945,0.89954132424960243,0.26099093454048067,1.1005009742727014,0.96403951655735221,0.96516596775583285,0.2734454024019124,0.33245330386656824);
        attribute :>> routeMargins = (3.3539169888293774,0.0065694861937930504,0.056210160244829499,3.0065694861937935,0.35391698882937783,0.23750941388820612);
        attribute :>> restoringMomentsNm = (22.493872954339402,24.158515344731363,22.498170811429766,24.100789441545356);
    }
    analysis nominalReview : BlueDogSizingEvidence::Review { subject :>> scenario = nominal; }
    part construction : BlueDogSizingEvidence::Scenario {
        attribute :>> label = "construction";
        attribute :>> numericallyBalanced = true;
        attribute :>> missingPitchRoots = 0;
        attribute :>> pitchUnstableSamples = 86;
        attribute :>> diagnosticControlCases = 0;
        attribute :>> easterlyHours = 68.963211336291593;
        attribute :>> westerlyHours = 55.9130957861287;
        attribute :>> massKg = 33.105645195552896;
        attribute :>> evidenceAccepted = false;
        attribute :>> operatingMargins = (-2.729905190790305e-13);
        attribute :>> structuralMargins = (0.92774058392461622,0.582530459248499,0.71651081726844024,0.30233550151466004,0.85626285066536822,-0.25899904624574943,-0.37490864339433827,-0.34306198499446139,0.73466202647425916,0.027406709157772324,0.25417528189148164,0.67350924431629999,-0.022478676976586565,0.88775113773194525,1.3104061488983119,0.80441256912775128,0.25922506131558137,1.1005009742727014,0.96275800136512646,0.96274558049686976,0.18037988867479504,0.26013957342803928);
        attribute :>> routeMargins = (3.3230767022011154,-0.0099216408359179553,0.042177620329283405,2.990078359164082,0.32307670220111584,0.22342922519265696);
        attribute :>> restoringMomentsNm = (22.647259365581739,24.40436521217109,22.65182068067374,24.343117811403939);
    }
    analysis constructionReview : BlueDogSizingEvidence::Review { subject :>> scenario = construction; }
    part aerodynamic : BlueDogSizingEvidence::Scenario {
        attribute :>> label = "aerodynamic";
        attribute :>> numericallyBalanced = true;
        attribute :>> missingPitchRoots = 0;
        attribute :>> pitchUnstableSamples = 86;
        attribute :>> diagnosticControlCases = 0;
        attribute :>> easterlyHours = 91.881941680698603;
        attribute :>> westerlyHours = 56.868141417534666;
        attribute :>> massKg = 31.447719266406427;
        attribute :>> evidenceAccepted = false;
        attribute :>> operatingMargins = (-2.3098361197071425e-08);
        attribute :>> structuralMargins = (0.94543513836936344,0.66837739039140598,0.793811093735875,0.48102813749816431,0.89146433697702698,8.0834283378017346e-08,-6.0907544834343241e-06,0.00093615008183722814,0.75999985862045649,-8.8362227712579511e-07,0.30885760961849151,0.69084260925563856,-1.5261190828841364e-06,0.90378668948452445,1.3527871062958945,0.89954132424960243,0.26099093454048067,1.1005009742727014,0.96403951655735221,0.96516596775583285,0.2734454024019124,0.33245330386656824);
        attribute :>> routeMargins = (3.327026185423728,-0.29714538578115279,-0.27613807889859165,2.7028546142188472,0.32702618542372841,0.2101647025342408);
        attribute :>> restoringMomentsNm = (22.493872954339402,24.158515344731363,22.498170811429766,24.100789441545356);
    }
    analysis aerodynamicReview : BlueDogSizingEvidence::Review { subject :>> scenario = aerodynamic; }
    part hydrodynamic : BlueDogSizingEvidence::Scenario {
        attribute :>> label = "hydrodynamic";
        attribute :>> numericallyBalanced = true;
        attribute :>> missingPitchRoots = 0;
        attribute :>> pitchUnstableSamples = 86;
        attribute :>> diagnosticControlCases = 0;
        attribute :>> easterlyHours = 72.348545855704302;
        attribute :>> westerlyHours = 58.322366218346858;
        attribute :>> massKg = 31.447719266406427;
        attribute :>> evidenceAccepted = false;
        attribute :>> operatingMargins = (-5.2153836804791358e-13);
        attribute :>> structuralMargins = (0.94543513836936344,0.66837739039140598,0.793811093735875,0.48102813749816431,0.89146433697702698,8.0834283378017346e-08,-6.0907544834343241e-06,0.00093615008183722814,0.75999985862045649,-8.8362227712579511e-07,0.30885760961849151,0.69084260925563856,-1.5261190828841364e-06,0.90378668948452445,1.3527871062958945,0.89954132424960243,0.26099093454048067,1.1005009742727014,0.96403951655735221,0.96516596775583285,0.2734454024019124,0.33245330386656824);
        attribute :>> routeMargins = (3.2566035818493404,-0.063095581478009866,-0.0048409146625596478,2.9369044185219901,0.25660358184934084,0.18996713585629366);
        attribute :>> restoringMomentsNm = (22.493872954339402,24.158515344731363,22.498170811429766,24.100789441545356);
    }
    analysis hydrodynamicReview : BlueDogSizingEvidence::Review { subject :>> scenario = hydrodynamic; }
    part energy : BlueDogSizingEvidence::Scenario {
        attribute :>> label = "energy";
        attribute :>> numericallyBalanced = true;
        attribute :>> missingPitchRoots = 0;
        attribute :>> pitchUnstableSamples = 86;
        attribute :>> diagnosticControlCases = 8;
        attribute :>> easterlyHours = 67.936040275364761;
        attribute :>> westerlyHours = 54.725803496072416;
        attribute :>> massKg = 31.447719266406427;
        attribute :>> evidenceAccepted = false;
        attribute :>> operatingMargins = (-0.59538548401096325);
        attribute :>> structuralMargins = (0.94543513836936344,0.66837739039140598,0.793811093735875,0.48102813749816431,0.89146433697702698,8.0834283378017346e-08,-6.0907544834343241e-06,0.00093615008183722814,0.75999985862045649,-8.8362227712579511e-07,0.30885760961849151,0.69084260925563856,-1.5261190828841364e-06,0.90378668948452445,1.3527871062958945,0.89954132424960243,0.26099093454048067,1.1005009742727014,0.96403951655735221,0.96516596775583285,0.2734454024019124,0.33245330386656824);
        attribute :>> routeMargins = (3.3596666637101062,0.0065694861769212132,0.056443885064378363,3.0065694861769217,0.35966666371010625,0.23991939588788314);
        attribute :>> restoringMomentsNm = (22.493872954339402,24.158515344731363,22.498170811429766,24.100789441545356);
    }
    analysis energyReview : BlueDogSizingEvidence::Review { subject :>> scenario = energy; }
    part combined : BlueDogSizingEvidence::Scenario {
        attribute :>> label = "combined";
        attribute :>> numericallyBalanced = true;
        attribute :>> missingPitchRoots = 0;
        attribute :>> pitchUnstableSamples = 86;
        attribute :>> diagnosticControlCases = 8;
        attribute :>> easterlyHours = 3842.0473089633233;
        attribute :>> westerlyHours = 106.52360358013347;
        attribute :>> massKg = 33.105645195552896;
        attribute :>> evidenceAccepted = false;
        attribute :>> operatingMargins = (-0.59537663254393447);
        attribute :>> structuralMargins = (0.92774058392461622,0.582530459248499,0.71651081726844024,0.30233550151466004,0.85626285066536822,-0.25899904624574943,-0.37490864339433827,-0.34306198499446139,0.73466202647425916,0.027406709157772324,0.25417528189148164,0.67350924431629999,-0.022478676976586565,0.88775113773194525,1.3104061488983119,0.80441256912775128,0.25922506131558137,1.1005009742727014,0.96275800136512646,0.96274558049686976,0.18037988867479504,0.26013957342803928);
        attribute :>> routeMargins = (3.5994024503321409,-0.98549451350569939,-52.361768180046155,3.0145054864943006,-0.40059754966785954,-0.47949449416852041);
        attribute :>> restoringMomentsNm = (22.647259365581739,24.40436521217109,22.65182068067374,24.343117811403939);
    }
    analysis combinedReview : BlueDogSizingEvidence::Review { subject :>> scenario = combined; }
    dependency candidateBasis from candidate to BlueDogDesignDecisions::sizingBaseline;
}
