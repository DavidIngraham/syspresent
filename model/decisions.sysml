package SyspresentDecisions {
    comment projectIntake /* Open the demo at a landing page with demo selection and local source/folder/ZIP import. Basic exploration requires only model sources and necessary custom libraries. The optional v2 project descriptor records title and navigation or publication intent; file lists, native root and requirement indexes, engine versions and hashes are discovered or generated. Native parsing remains authoritative. Read portable v1 projects without rewriting frozen snapshots. Story and presentation-owned views remain ordinary optional author files. */
    doc /* Owner-agreed product and architecture direction, 19 October 2026. Decisions describe intended behavior; they do not establish implemented capability or verification evidence. */
    comment defaultPublication /* The canvas application is the sole Syspresent viewer and is served directly at the GitHub Pages project root. Publication replaces the deployed site with the validated canvas build; retired viewer pages, catalogs and snapshot routes are not published. Retain canvas review archives by content digest and source history in Git. Making canvas the default does not establish full-product acceptance. */
    comment semanticRuntime /* OpenSysML Go is the semantic engine, hosted as WASM in a browser worker and natively in CI. Syspresent owns a new interactive canvas through a versioned semantic/view adapter. The VS Code extension source is not a dependency of the new canvas architecture. Keep OMG repository access as a possible future adapter rather than a required backend. */
    comment graphVersusModel /* A scoped view projection is not the complete model graph. Keep model identity, diagram representation identity, scene intent, calculated layout and transition correspondence distinct. Preserve behavior-specific information from native processing; never reconstruct engineering meaning from labels. */
    comment dynamicCanvas /* The graph canvas is the primary interface in both standalone exploration and guided stories. Every scene may rearrange freely for visibility; semantic identity and reader focus persist rather than global coordinates. Settled scenes remain steady while read. Active content controls fit and centering; translucent one-hop context occupies a prepared world around active content, including offscreen tiles, and never enlarges the initial active fit bounds. Camera pan and zoom reveal that world without relayout or recursive expansion. Every included neighbor has a real tile; viewport clipping does not create a continuation endpoint. */
    comment narrativeSpace /* Floating Markdown panels are measured layout occupants. Their size and placement may change between scenes and viewport sizes; the diagram layout must account for their actual area. Panel anchors express semantic association without forcing the panel to move on every node movement. */
    comment journeys /* Same-notation changes with shared semantic content gather, fade and relayout directly. Disjoint same-notation contexts also use a GV journey. Use one continuous animation clock across intermediate viewpoints rather than separately eased stop-and-start stages. Entering and leaving nodes, relationships and narrative fade. A departing tile vacates a replacement region by moving off frame and fading before the replacement enters; exit sweeps avoid retained tiles and prose or fade before contact when blocked. Held arrivals start smoothly. Scheduling applies within each adjacent viewpoint interval and preserves intermediate native waypoint visibility. Cross-notation transitions pass through GV, travel meaningful engineering relationships, gather the destination features and morph into the new notation. Automatic journeys ascend actual directed engineering links to the nearest common ancestor, then descend. Native project ownership provides a separately labeled location fallback; it is not engineering derivation. Each journey shows bounded local windows and retains native edge directions. No permitted ancestor means a disclosed explicit jump. Proposed routes are author-editable and saved explicitly, and invalid saved routes fail validation for every diagram type. The presentation declares a system of interest with scene additions; shared KerML or library ancestry never creates an automatic shortcut. */
    comment modelViews /* Reusable selection belongs in SysML view definitions and usages with native executable semantics. Markdown references those views and owns narrative, scene order, emphasis and transition choreography. Do not duplicate a model query/traversal language in Markdown. Rendering intent in SysML does not itself implement JavaScript layout or animation. */
    comment readerInteraction /* First click, tap or keyboard selection highlights and reveals contextual actions. Only an explicit action changes focus or expands the graph. Departing a guided scene collapses prose into Return to scene; returning restores its authored viewpoint and content. */
    comment requirementQuestions /* Statement, rationale, origins, system impact and verification are questions answered through diagram compartments, annotations and selected relationships. The rejected separate requirement-question reader is not the default architecture. Preserve explicit definition-to-usage typing and native relationship direction. */
    comment authoring /* Editing mode runs on the static site. Authors import a project, explore and capture viewpoints, edit narrative and views, and export ordinary files or a ZIP. Underlying system model authoring is deferred; authored view definitions remain editable. Markdown can also be imported or exported independently. */
    comment coverage /* Include the complete project by default. Explicit scoped publications remain supported and disclose unavailable targets separately from hidden content. Stories guide loaded-model traversal without becoming hard exploration barriers. */
    comment snapshots /* Preserve immutable story, model, evidence and runtime snapshots. Rebuild validation reports broken references; deep change history, automatic semantic adjudication and mandatory reapproval on model updates are not current work. Existing catalog lifecycle records do not establish engineering approval. */
    comment notation /* Preserve the broad product notation requirements: structure, requirements, activities, sequences, states, fault trees and native tables. A small GV-to-other-notation prototype proves the new contract without claiming complete notation support or replacing the reader study. Multiple regions may coexist with visible notation boundaries. */
    comment generalViewOrder /* General structural views place classifiers and general definitions above typed usages and specializations by default, preserving native arrows. Source requirements appear above derivations or refinements; satisfying parts and verifying cases appear below their requirements. Visual decision-chain rank does not assert model ownership. Authored constraints may adjust this. Behavioral and fault-tree views retain their semantic ordering. */
    comment scopedMilestone /* The immediate milestone proves real native/WASM identity and view parity, focused engineering traversal, a GV gather-to-other-notation transition, measured Markdown space and capture/export of a scene using an unrelated small model. This is a prototype milestone, not completion of the earlier whole-product goal. */
    comment connectionRouting /* Use ELK as a disposable joint geometry engine in a browser worker, with native OpenSysML identities and relationship endpoints unchanged. Structural siblings may stagger or change order for readability; behavior concurrency and actual model ports retain their native meaning. Display anchors are not model ports. Relationship selection traces its route and endpoints without rearranging the scene. Prefer short low-bend structural routes using the actual facing sides, while reserving distinct native terminals and measured labels. Translucent context routes participate in crossing and overlap minimization against active corridors and each other. Preserve active geometry; route to actual neighboring tiles in an extensible world and disclose residual conflicts or unavailable routes. Do not replace offscreen tiles with short continuations; never merge distinct relationships into an apparent junction. Revalidate moving connection paths against tile obstacles and their current endpoints instead of interpolating through tiles or leaving floating wires. Invisible routes have no pointer or keyboard targets. */
    comment focusedRequirementTraversal /* Requirement selection offers directional origins, derived requirements, system impact and verification actions on the existing canvas. Traverse actual native links with at most one explicit requirement definition/usage typing bridge. Bounded result pages disclose their limits; missing projected links do not prove model absence. Back and Forward restore focus, native view, scene handoff, expanded statements and presentation preferences. Display preferences in Markdown control compartments, edge emphasis, peripheral budget and soft sibling ordering by actual owner, without replacing native selection or inventing containment. */
    comment focusedStructure /* The October 28 correction supersedes the earlier effective-requirements structural default. Explicit Focus opens complete immediate declarations for every source declaration kind; packages open isolated contents. Effective requirements, local understanding and global impact remain explicit semantic actions. Native ownership and one direct typing bridge preserve classifier identity without runtime instantiation, recursive ancestry or related-node displacement. Engineering trace paging remains distinct from sibling completeness. */
    comment neighborhoodCamera /* Neighbor inclusion is separate from viewport fitting. Default to 48 one-hop neighbors on every screen size, with native relationship priorities appropriate to parts, packages or requirements and a deterministic balanced allocation around the active nodes with the focus first. Authors may set zero through 256; readers may explicitly increase a reached limit. Native package ownership is shown in structural contexts, while requirement ownership stays opt-in. Show neighborhood frames the prepared world; Fit restores the active content. Pinch, drag, wheel, keyboard and visible zoom controls change only the camera. Selection remains stationary; Focus promotes a neighbor and rearranges its new active neighborhood. History restores camera and neighborhood limit. Prose and controls remain in screen space outside the graph camera. */
    comment regionRenderers /* One presentation workspace hosts graph, sequence and grid renderers. Each exposes represented identities, selection targets, transition anchors and restorable navigation state. Native grid column and cell identities come from the Go engine, retaining every relationship occurrence and its matrix direction. Matrix derivation axes are original-to-derived; graph diagram conventions shall not silently reverse those records. Grid-only relations do not augment general ancestry routing without an explicit direction adapter. Comparison regions coordinate selection and preserve independent navigation. Small screens use tabs rather than shrinking grids. */
    comment readerControls /* All optional compartments are shown by default. Reader All/None/Focused and Square/Mind-map controls persist in local browser storage and override authored initial display preferences. A first selection remains stationary. Compartment controls cannot suppress mandatory native behavior notation. Curves change geometry only and preserve actual native endpoints and markers. */
    comment automaticOverview /* Authored scenes retain intentional membership. Manual Explore leaves that sample and opens selected part contents or the nearest native containing package. Packages display every immediate source declaration. Whole project displays actual native document/source roots, following owners through relationship records. Relationship-owned metadata and missing/cyclic boundaries use explicit source inspection; annotation targets never become parents. No prominence, named-only or viewport budget chooses default siblings. Readable world-scale grids use pan/zoom and keyboard reveal; ownership frames retain native provenance. Selection is stationary and navigation/history restores complete membership. */
    comment packageWorkspace /* Package scope is independent of focus and presentation roots. Follow native ownership only; expose a searchable picker, visible scope, Up, Whole project and complete immediate Contents. Preserve scope through search, traces, native view switches and history. Native views crossing scope are rejected intact before replacing the viewpoint. Whole project is the loaded source ownership projection, not merely story roots. The full project remains loaded; scope is not publication exclusion or proof of absent links. */
    comment deferred /* Underlying system-model editing, shared accounts/collaboration, a required backend, deep model history, automatic model diffs and mandatory change-review workflows are deferred. Full-product notation coverage, complete portable-project editing and human usability acceptance require separate evidence beyond the prototype. */
    comment canvasStoryContent /* Extend scene Markdown with optional contiguous chapter metadata, bundled figure regions and model-linked context cards. Retain native views as the primary scene and model selection authority. Figures use inert browser image elements, source/caption metadata and native reference buttons; narrow layouts reuse region tabs. Context categories are authored reading aids, never inferred statuses. Browser and publication validation share the reference/content contract. Demo archives carry a content digest in scene links; imported or edited projects share by ZIP until hosted. Chapter links and Contents preserve scene order; browser Back/Forward restores direct scene navigation. Full value substitution, interactive charts, reading-before-engine startup and continuous document export remain separate work. */
    comment recoveredVoiceDirection /* Recovered October 25-26 conversation requested complete hierarchy, attribute/part canvas content and effective requirement understanding. The October 28 explicit correction requires complete default canvas siblings rather than four/five samples or sidebar-only access, and takes precedence for structural default entry. Effective requirements remains an explicit collapsed-inheritance action. Questions append native slides only on submission. Captures are native definitions/usages validated before mutation. Provider/API/privacy/credentials remain undecided and unconfigured. */
    comment exploratoryLayoutState /* Store presentation positions in syspresent-layouts.json, a portable inert project asset separate from SysML selection and story narrative. Use semantic/representation and containing-semantic identities plus normalized offsets; never pin to a model hash or serialize a viewport screenshot. Export ZIP is the durable-save boundary; no automatic browser retention of model metadata is introduced. Preserve layout snapshots in navigation history and rebind captures only through unique native correspondence. Structural groups move rigidly with descendants and actual ports. Nested structural and state movement stays inside actual fitted parent-body bounds below its header, with native port-label and collision checks. Mapped action/control and fault-tree nodes may move horizontally to preserve established drawing reading layers; horizontal positions do not define modeled lanes or branch order. Complete native behavioral containers may move rigidly when external succession does not constrain their layer. Synthetic controls and actual ports move with their owning container. Unsafe routes, missing parent bounds and loss of mandatory native relationship labels reject movement explicitly. Dedicated sequence/grid regions save only typed lane widths, message spacing and column widths, retaining native identities, native participant order, explicit event successions and matrix direction. Displayed message order remains a native-provided partial-order linearization; no ordinate asserts elapsed time or an additional modeled total order. */
    comment focusedNotationPolicy /* Exploratory is default. Focused notation removes peripheral context, edge emphasis and exploratory journeys while retaining the native active view. It does not certify full OMG conformance. Official SysML 2.0 Language formal/2026-03-02 section 8.2.3 is the notation reference; remaining unsupported symbols, data-blocked endpoint roles and native rendering extensions require disclosure. Inventory all actual supplied native views and keep emitted-record counts, helper support, browser checks and conformance claims separate; a native-base rendering does not certify an extension symbol. Typed native relationship rollups remain exploratory drawing artifacts and are disabled in focused mode. Live LLM generation remains unavailable until an explicit provider/privacy decision and authorized transport configuration. */

    comment nativeRollupIdentity /* Roll up actual directed native links through native owner paths only, grouping by native relationship kind. Retain distinct known relationship identities and every API/view occurrence; never count repeated projections as extra modeled relationships. Unresolved native relationship identity is disclosed as connection records. Explicit drilldown rechecks current ownership, availability and reader scope. Aggregates never enter native capture, semantic traversal or modelGraph. Native satisfaction IDs are recognized only when the engine maps them to actual SatisfyRequirementUsage objects, not from endpoint labels. */
    comment nativeAuthoringBoundary /* Use structured provider-neutral proposals that generate actual native view definitions/usages and native type filters. Validate parse/render membership, scope, exact native references and directed claims before applying an author draft. Closed generated-view validation may reuse the loaded native source identity/documentation index only while existing source bytes and view-file ownership remain unchanged; candidate native parsing/rendering and fresh candidate value queries remain mandatory. This reuse creates no publisher-trusted cache; edited-project reindexing still uses the native declaration exporter. Native documentation and GetSymbol static attribute values supply reusable narrative bindings on reload/build. If a known attribute has no static value, evaluate only that exact quoted attribute in its explicitly selected native owner/subject context, retaining the native result, diagnostics and provenance. Support typed finite scalars, exact large integers, native quantities and canonical enumeration identities when supplied. Do not expose arbitrary evaluation text, supply missing inputs, run actions or simulations, infer units from names, or silently convert units. Unset, undetermined and collection results remain rejected scalar substitutions. Local starters are not LLM output, test mocks remain labeled, and no provider, credentials, paid calls or external model-data transmission are configured. Free prose remains an unverified author draft even when its structured references are checked. */

    comment nativeModelMemory /* Keep semantic selection separate from memory management. Native declaration projection retains every source-backed object and its ordered values while avoiding annotation work for omitted subjects. The application owns explicit native model leases for the current project, compilation and reviewed candidates; in-flight requests pin their exact model until completion. Release intermediate and superseded state only after its last owner and request finish, with atomic disposal across validation and execution caches. Rejected or stale loads retain the current model. Optional native memory diagnostics distinguish live heap from acquired arenas; WASM linear memory grows in pages and does not shrink when objects are released. Reuse freed space across repeated edits instead of retaining every model version until a count-based cache fills. */

    comment startupFeedback /* Begin one revision-scoped loading operation for each explicit project choice. Show measured stage counts separately from indeterminate native work, retain retry inputs locally and ignore stale progress/errors. Overlap the selected project download with a single streaming semantic-engine initialization; do not initialize a model on the untouched landing page. Cache JSON reuse is limited to one load and still rehashes current bytes and verifies native source/model identity. A dead worker owns no live native models; initial cancellation may terminate it only when no accepted previous model depends on it. Normal model replacement retains existing leases until a new initial view commits. Optimize route search without changing its candidate set, tie order, geometry or semantic identities. Physical-device acceptance and deployment approval remain separate from local software evidence. */

    comment canonicalModelImports /* Import a committed namespace migration by exact source hashes and explicit qualified-ID mapping. Replace obsolete project documents rather than append duplicate fragments; retain independent reusable libraries and all source bytes. Native ownership and identity remain authoritative. Viewer helper packages and projection-boundary entries are distinct from upstream model roots. Preserve historical evidence/run provenance while migrating live native bindings. Rebuild and validate native snapshots after source replacement; source copying alone does not establish rendered completeness or engineering acceptance. */
    comment metadataInspection /* Check actual visible root identities, not package inventory alone. Dependency owners exist in the native export; filtering them from structural drawing must not promote their metadata to root cards. Keep owner, annotatedElement and annotation-record provenance distinct. Searchable/pageable metadata inspection retains every source identity and exact counts. Node/relationship inspection is stationary; explicit Contents reveals actual owned fields. Native document roots persist through graph rebuilds and caches. Missing/cyclic ownership uses Source inspection. */
}
