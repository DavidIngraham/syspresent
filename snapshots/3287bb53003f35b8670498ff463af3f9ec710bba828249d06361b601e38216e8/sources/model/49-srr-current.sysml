// Generated by tools.publishing.srr from immutable run evidence.
package BlueDogSRRCurrent {
    private import ScalarValues::*;
    attribute evidenceManifest : String = "evidence/runs/2026-10-13-srr-readiness/manifest.json";
    part candidate {
        attribute batteryWh : Real = 440.0;
        attribute hullBeamM : Real = 0.26;
        attribute massKg : Real = 10.312830010265998;
        attribute westerlyPassageHours : Real = 33.86883519742054;
        attribute departureWh : Real = 316.8;
        attribute requiredWh : Real = 312.82633955094434;
        attribute energyHeadroomWh : Real = 3.9736604490556715;
        attribute balanced : Boolean = true;
        attribute staticScreensPass : Boolean = true;
        attribute physicallyQualified : Boolean = false;
        doc /* Retained concept with revised battery capacity and hull beam; nominal refined static replay.
         * Not a new optimum, hardware selection, dynamic recovery proof or mission qualification. */
    }
    part energyInputs {
        attribute sourceRevision : String = "b2aa167bc0a2cd7958246e20f70a227bc257bc39";
        attribute resinGlassRatio : Real = 1.0;
        attribute gearboxEfficiency : Real = 0.4;
        attribute motorEfficiency : Real = 0.8;
        attribute wingNoLoadW : Real = 1.0;
        attribute wingControllerW : Real = 0.1;
        attribute wingMotorHoldingW : Real = 0.0;
        attribute wingMoveFraction : Real = 0.02;
        attribute wingHoldingFraction : Real = 0.98;
        attribute rudderHoldingWPerNm : Real = 0.5;
        attribute rudderMoveFraction : Real = 0.05;
        attribute electronicsW : Real = 4.570486111111111;
        attribute solarResourceFactor : Real = 0.6;
        attribute batteryWhKg : Real = 140.0;
        attribute laminateKnockdown : Real = 1.0;
        attribute profileCd : Real = 0.04;
        attribute wingClLimit : Real = 0.9;
        attribute wingLiftScale : Real = 0.7;
        attribute wingDragScale : Real = 1.4;
        attribute wingRateRadS : Real = 0.25;
        attribute rudderRateRadS : Real = 0.6;
        attribute driveKgPerNm : Real = 0.15;
        attribute wingDriveBaseKg : Real = 0.2;
        attribute fixedEquipmentKg : Real = 2.5;
        attribute attachmentKg : Real = 0.6;
        attribute residuaryResistanceFactor : Real = 1.0;
        attribute viscousFormFactor : Real = 1.15;
        attribute foilClLimit : Real = 0.8;
        attribute foilEfficiency : Real = 0.7;
        attribute foilCd : Real = 0.012;
        attribute airNu : Real = 1.5e-05;
        attribute waterNu : Real = 1e-06;
        attribute waterDensity : Real = 1000.0;
        attribute airDensity : Real = 1.225;
        attribute ballastDensity : Real = 7800.0;
        attribute gravity : Real = 9.80665;
        attribute loadFactor : Real = 1.5;
        attribute assemblyLimitKg : Real = 15.0;
        attribute panelCoverage : Real = 0.6;
        attribute elevatedEquipmentKg : Real = 0.15;
        attribute elevatedEquipmentXFraction : Real = 0.0;
        attribute elevatedEquipmentAboveDeckM : Real = 0.3;
        attribute windBusW : Real = 0.07048611111111112;
        attribute durationMultiplier : Real = 1.25;
        attribute delayHours : Real = 6;
        attribute dischargeEfficiency : Real = 0.9;
        attribute usableFraction : Real = 0.8;
        attribute initialFraction : Real = 0.9;
        attribute selfDischargeW : Real = 0.02;
        attribute reserveWh : Real = 49.2;
    }
    part def EnergyCase {
        attribute label : String;
        attribute wingTorqueNm : Real;
        attribute rudderTorqueNm : Real;
        attribute recordedAverageW : Real;
        attribute recordedPeakW : Real;
    }
    part energyCase0 : EnergyCase {
        attribute :>> label = "5 m/s, windward, tack 1";
        attribute :>> wingTorqueNm = 0.09863444356620701;
        attribute :>> rudderTorqueNm = 0.05393485166632078;
        attribute :>> recordedAverageW = 4.869668885770823;
        attribute :>> recordedPeakW = 6.887995408896952;
    }
    part energyCase1 : EnergyCase {
        attribute :>> label = "5 m/s, windward, tack -1";
        attribute :>> wingTorqueNm = 0.09123004428899213;
        attribute :>> rudderTorqueNm = 0.05523090754102247;
        attribute :>> recordedAverageW = 4.870217420667901;
        attribute :>> recordedPeakW = 6.883182763867653;
    }
    part energyCase2 : EnergyCase {
        attribute :>> label = "5 m/s, leeward, tack 1";
        attribute :>> wingTorqueNm = 0.03252642271323138;
        attribute :>> rudderTorqueNm = 0.030308416903813272;
        attribute :>> recordedAverageW = 4.85652740012921;
        attribute :>> recordedPeakW = 6.818628691533684;
    }
    part energyCase3 : EnergyCase {
        attribute :>> label = "5 m/s, leeward, tack -1";
        attribute :>> wingTorqueNm = 0.05496520460434538;
        attribute :>> rudderTorqueNm = 0.029163488989072714;
        attribute :>> recordedAverageW = 4.856291230539954;
        attribute :>> recordedPeakW = 6.835300293950061;
    }
    part energyCase4 : EnergyCase {
        attribute :>> label = "8 m/s, windward, tack 1";
        attribute :>> wingTorqueNm = 0.5517728761051918;
        attribute :>> rudderTorqueNm = 0.07956789220334846;
        attribute :>> recordedAverageW = 4.889886107054471;
        attribute :>> recordedPeakW = 7.261234589720804;
    }
    part energyCase5 : EnergyCase {
        attribute :>> label = "8 m/s, windward, tack -1";
        attribute :>> wingTorqueNm = 0.5517728761052052;
        attribute :>> rudderTorqueNm = 0.0810173703045101;
        attribute :>> recordedAverageW = 4.890628964581317;
        attribute :>> recordedPeakW = 7.262321698296685;
    }
    part energyCase6 : EnergyCase {
        attribute :>> label = "8 m/s, leeward, tack 1";
        attribute :>> wingTorqueNm = 0.05571530282314596;
        attribute :>> rudderTorqueNm = 0.053792082393333496;
        attribute :>> recordedAverageW = 4.8689251049443065;
        attribute :>> recordedPeakW = 6.854357753236695;
    }
    part energyCase7 : EnergyCase {
        attribute :>> label = "8 m/s, leeward, tack -1";
        attribute :>> wingTorqueNm = 0.11945081411444261;
        attribute :>> rudderTorqueNm = 0.050200672313092345;
        attribute :>> recordedAverageW = 4.868080374642109;
        attribute :>> recordedPeakW = 6.901457563872839;
    }
    alias energyGoverningCase for energyCase5;
    alias peakGoverningCase for energyCase5;
    dependency energyBasis from candidate to BlueDogConceptCredibility::passagePolicy;
    dependency recoveryBasis from candidate to BlueDogRequirements::lowEnergyRecovery;
}
