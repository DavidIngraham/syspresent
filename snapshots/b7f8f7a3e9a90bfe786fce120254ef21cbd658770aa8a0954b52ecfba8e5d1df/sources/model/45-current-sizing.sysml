// Generated by tools.boat_analysis.evidence.model; edit source evidence only through a new recorded run.
package BlueDogCurrentSizing {
    private import ScalarValues::*;
    doc /* Exploratory run at source revision 6716c9a12301ba3c91d1ceb2190de4ef00a884f9.
     * Evidence: evidence/runs/2026-10-12-bingen/manifest.json.
     * Finite Gorge challenge rerun; publishing this projection does not execute a new solve. */
    part candidate : MarineDesign::Design {
        attribute :>> length_m = 2.009273606288621;
        attribute :>> beam_m = 0.60794480099882087;
        attribute :>> bottom_depth_m = 0.052980023908892906;
        attribute :>> deck_height_m = 0.16285437007218445;
        attribute :>> sail_m2 = 1.1749947436992398;
        attribute :>> sail_AR = 2.9897220605843415;
        attribute :>> camber_scale = 1.0001651734277246;
        attribute :>> wing_thickness_scale = 1.2029291216922127;
        attribute :>> mast_fraction = 0.50015640304676856;
        attribute :>> mast_x_fraction = -0.017055895322377945;
        attribute :>> keel_m2 = 0.14785705608104413;
        attribute :>> keel_span_m = 0.70810230340354718;
        attribute :>> rudder_m2 = 0.01250616472159935;
        attribute :>> rudder_span_m = 0.12822691546838755;
        attribute :>> rudder_arm_fraction = 0.49984320901592999;
        attribute :>> ballast_kg = 11.668930280578605;
        attribute :>> battery_Wh = 208.20669848542397;
        attribute :>> panel_m2 = 0.23097609955017351;
        attribute :>> wing_torque_Nm = 0.84581422481627055;
        attribute :>> rudder_torque_Nm = 0.81439501073520648;
        attribute :>> hull_glass_kg_m2 = 0.60341709609082861;
        attribute :>> wing_glass_kg_m2 = 0.45241145604172167;
        attribute :>> keel_glass_kg_m2 = 4.80809991405666;
        attribute :>> rudder_glass_kg_m2 = 0.60281995032794811;
        attribute :>> hull_rib_pitch_m = 0.029734176171558116;
        attribute :>> foil_rib_pitch_m = 0.04046312096151844;
        attribute :>> battery_x_fraction = -0.34649999999999992;
        attribute :>> battery_z_fraction = 0.099963514620108593;
        attribute :>> hull_fullness_exponent = 1.8000691642287374;
    }
    part searchAssessment {
        attribute solverStatus : String = "Iteration limit reached";
        attribute activeBounds : String = "none";
        attribute coarseFeasible : Boolean = true;
        attribute massKg : Real = 33.441655552026205;
        attribute maximumResidual : Real = 1.9663214043119659e-08;
        attribute minimumMargin : Real = -1.2707505936404573e-08;
        attribute progressReserveMps : Real = 0.0050000000000000001;
        attribute qualified : Boolean = false;
    }
    part searchConstraint0 {
        attribute label : String = "keelDeflectionMargin";
        attribute margin : Real = -1.2707505936404573e-08;
    }
    part searchConstraint1 {
        attribute label : String = "wingDeflectionMargin";
        attribute margin : Real = -7.6129478276953932e-09;
    }
    part searchConstraint2 {
        attribute label : String = "case 4: wingDriveMargin";
        attribute margin : Real = -2.9918589827815367e-09;
    }
    part searchConstraint3 {
        attribute label : String = "case 0: delftDomain6 (search reserve)";
        attribute margin : Real = 0;
    }
    part searchConstraint4 {
        attribute label : String = "case 1: delftDomain6 (search reserve)";
        attribute margin : Real = 0;
    }
    part searchConstraint5 {
        attribute label : String = "case 2: delftDomain6 (search reserve)";
        attribute margin : Real = 0;
    }
    part searchConstraint6 {
        attribute label : String = "case 3: delftDomain6 (search reserve)";
        attribute margin : Real = 0;
    }
    part searchConstraint7 {
        attribute label : String = "case 4: delftDomain6 (search reserve)";
        attribute margin : Real = 0;
    }
    part searchConstraint8 {
        attribute label : String = "case 5: delftDomain6 (search reserve)";
        attribute margin : Real = 0;
    }
    part searchConstraint9 {
        attribute label : String = "case 6: delftDomain6 (search reserve)";
        attribute margin : Real = 0;
    }
    part searchConstraint10 {
        attribute label : String = "case 7: delftDomain6 (search reserve)";
        attribute margin : Real = 0;
    }
    part searchConstraint11 {
        attribute label : String = "case 0: delftDomain15 (search reserve)";
        attribute margin : Real = 0.0020000000000154339;
    }
    part convergence0 {
        attribute label : String = "forward, beta 0, wake";
        attribute passesScreen : Boolean = true;
        attribute CLtot : Real = 0.0010974820100000393;
        attribute CDi : Real = 0.00084670703500000499;
        attribute CMytot : Real = 0.00020432221599998857;
    }
    part convergence1 {
        attribute label : String = "forward, beta 0, mesh";
        attribute passesScreen : Boolean = true;
        attribute CLtot : Real = 0.017708813035000048;
        attribute CDi : Real = 0.0064258317499999995;
        attribute CMytot : Real = 0.0031552284759999993;
    }
    part convergence2 {
        attribute label : String = "reverse, beta 0, wake";
        attribute passesScreen : Boolean = true;
        attribute CLtot : Real = 0.001327419566000021;
        attribute CDi : Real = 0.00085670971500000082;
        attribute CMytot : Real = 0.00024245977799999818;
    }
    part convergence3 {
        attribute label : String = "reverse, beta 0, mesh";
        attribute passesScreen : Boolean = true;
        attribute CLtot : Real = 0.020571112351000065;
        attribute CDi : Real = 0.0053078105269999953;
        attribute CMytot : Real = 0.0033816664710000222;
    }
    part convergence4 {
        attribute label : String = "forward, beta 20, wake";
        attribute passesScreen : Boolean = true;
        attribute CLtot : Real = 0.0030444152249999856;
        attribute CDi : Real = 0.00093538887700000961;
        attribute CMytot : Real = 0.00074289939299999885;
    }
    part convergence5 {
        attribute label : String = "forward, beta 20, mesh";
        attribute passesScreen : Boolean = true;
        attribute CLtot : Real = 0.015921558743000053;
        attribute CDi : Real = 0.0030920898859999879;
        attribute CMytot : Real = 0.0028109218799999974;
    }
    part coarseGrid0 {
        attribute label : String = "forward, beta 0: mesh 24/wake 5 to mesh 72/wake 30";
        attribute CLtot : Real = 0.050497159055000074;
        attribute CDi : Real = 0.007092610272000005;
        attribute CMytot : Real = 0.0098591795550000139;
    }
    part coarseGrid1 {
        attribute label : String = "reverse, beta 0: mesh 24/wake 5 to mesh 72/wake 30";
        attribute CLtot : Real = 0.065062912521000049;
        attribute CDi : Real = 0.0035108145999999951;
        attribute CMytot : Real = 0.011013893448000023;
    }
    part coarseGrid2 {
        attribute label : String = "forward, beta 20: mesh 24/wake 5 to mesh 72/wake 30";
        attribute CLtot : Real = 0.048231737603000036;
        attribute CDi : Real = 0.0029270257569999902;
        attribute CMytot : Real = 0.0088007662020000016;
    }
    dependency assumptions from candidate to BlueDogAerodynamicPolicy::sizing;
    dependency convergenceBasis from convergence0 to BlueDogAerodynamicPolicy::convergenceInputs;
    part ingress0 {
        attribute label : String = "sealed, water 1000 kg/m3";
        attribute minimumRestoringNm : Real = 20.461024795165429;
        attribute missingPitchRoots : Integer = 0;
        attribute unstablePitchSamples : Integer = 78;
        attribute retainedWaterKg : Real = 0;
    }
    dependency ingressBasis0 from ingress0 to BlueDogRequirements::selfRighting;
    part ingress1 {
        attribute label : String = "free_flooding_homogenized, water 1000 kg/m3";
        attribute minimumRestoringNm : Real = -7.49090747036204;
        attribute missingPitchRoots : Integer = 0;
        attribute unstablePitchSamples : Integer = 0;
        attribute retainedWaterKg : Real = 0;
    }
    dependency ingressBasis1 from ingress1 to BlueDogRequirements::selfRighting;
    part ingress2 {
        attribute label : String = "full_water_retention, water 1000 kg/m3";
        attribute minimumRestoringNm : Real = -412.1378752582504;
        attribute missingPitchRoots : Integer = 0;
        attribute unstablePitchSamples : Integer = 7;
        attribute retainedWaterKg : Real = 46.16821699317093;
    }
    dependency ingressBasis2 from ingress2 to BlueDogRequirements::selfRighting;
    part ingress3 {
        attribute label : String = "sealed, water 1025 kg/m3";
        attribute minimumRestoringNm : Real = 20.666808275804474;
        attribute missingPitchRoots : Integer = 0;
        attribute unstablePitchSamples : Integer = 78;
        attribute retainedWaterKg : Real = 0;
    }
    dependency ingressBasis3 from ingress3 to BlueDogRequirements::selfRighting;
    part ingress4 {
        attribute label : String = "free_flooding_homogenized, water 1025 kg/m3";
        attribute minimumRestoringNm : Real = -7.8540319493918229;
        attribute missingPitchRoots : Integer = 0;
        attribute unstablePitchSamples : Integer = 0;
        attribute retainedWaterKg : Real = 0;
    }
    dependency ingressBasis4 from ingress4 to BlueDogRequirements::selfRighting;
    part ingress5 {
        attribute label : String = "full_water_retention, water 1025 kg/m3";
        attribute minimumRestoringNm : Real = -424.31304856120465;
        attribute missingPitchRoots : Integer = 0;
        attribute unstablePitchSamples : Integer = 7;
        attribute retainedWaterKg : Real = 47.322422418000208;
    }
    dependency ingressBasis5 from ingress5 to BlueDogRequirements::selfRighting;
    part nominal : BlueDogSizingEvidence::Scenario {
        attribute :>> label = "primary";
        attribute limitingScreens : String = "keelDeflectionMargin: -1.271e-08; wingDeflectionMargin: -7.613e-09; operating/peak power: -4.452e-13";
        attribute easterlyDownstreamMps : Real = 2.0648992805241333;
        attribute easterlyUpstreamMps : Real = 0.24861053884093698;
        attribute easterlyTimeLabel : String = if not numericallyBalanced or diagnosticControlCases > 0 ? "Diagnostic only" else if easterlyDownstreamMps <= 0 or easterlyUpstreamMps <= 0 ? "No completion (duration penalty)" else "41.18";
        attribute westerlyDownstreamMps : Real = 1.748610538840937;
        attribute westerlyUpstreamMps : Real = 0.5648992805241333;
        attribute westerlyTimeLabel : String = if not numericallyBalanced or diagnosticControlCases > 0 ? "Diagnostic only" else if westerlyDownstreamMps <= 0 or westerlyUpstreamMps <= 0 ? "No completion (duration penalty)" else "21.4";
        attribute :>> acceptanceRouteMargins = (2.497221077681874,0.12979856104826659,1);
        attribute :>> numericallyBalanced = true;
        attribute :>> missingPitchRoots = 0;
        attribute :>> pitchUnstableSamples = 78;
        attribute :>> diagnosticControlCases = 0;
        attribute :>> easterlyHours = 41.177205555190881;
        attribute :>> westerlyHours = 21.399871474949084;
        attribute :>> massKg = 33.451612629662762;
        attribute :>> evidenceAccepted = false;
        attribute :>> operatingMargins = (-4.4519943287468777e-13);
        attribute :>> structuralMargins = (0.96232046666456039,0.68797127438754957,0.78768408845980287,0.47436189159818165,0.93246005802610732,-7.6129478276953932e-09,-1.2707505936404573e-08,0.040182656049085219,0.76297477341939546,0.018534601818054219,0.21518622194779502,0.64969800630459118,0.0041543100012498835,0.90085395310217908,2.2319079760072187,1.4536495912113572,0.2822853511993289,1.1737992819589698,0.9694571871275337,0.9321174247116053,0.30103041231927197,0.70697633910527957);
        attribute :>> routeMargins = (3.1297985610482666,-0.50277892231812604,1,2.497221077681874,0.12979856104826659,1);
        attribute :>> restoringMomentsNm = (20.461024795165429,22.56743407497024,20.461140176385193,22.516756516316924);
    }
    analysis nominalReview : BlueDogSizingEvidence::Review { subject :>> scenario = nominal; }
    part construction : BlueDogSizingEvidence::Scenario {
        attribute :>> label = "construction";
        attribute limitingScreens : String = "keelDeflectionMargin: -0.3672; wingDeflectionMargin: -0.2598; rudderDeflectionMargin: -0.2325";
        attribute easterlyDownstreamMps : Real = 2.0285980753275306;
        attribute easterlyUpstreamMps : Real = 0.22571351097759995;
        attribute easterlyTimeLabel : String = if not numericallyBalanced or diagnosticControlCases > 0 ? "Diagnostic only" else if easterlyDownstreamMps <= 0 or easterlyUpstreamMps <= 0 ? "No completion (duration penalty)" else "44.98";
        attribute westerlyDownstreamMps : Real = 1.7257135109776001;
        attribute westerlyUpstreamMps : Real = 0.52859807532753078;
        attribute westerlyTimeLabel : String = if not numericallyBalanced or diagnosticControlCases > 0 ? "Diagnostic only" else if westerlyDownstreamMps <= 0 or westerlyUpstreamMps <= 0 ? "No completion (duration penalty)" else "22.58";
        attribute :>> acceptanceRouteMargins = (2.4514270219552001,0.057196150655061562,1);
        attribute :>> numericallyBalanced = true;
        attribute :>> missingPitchRoots = 0;
        attribute :>> pitchUnstableSamples = 76;
        attribute :>> diagnosticControlCases = 8;
        attribute :>> easterlyHours = 44.984646165700134;
        attribute :>> westerlyHours = 22.579982312648262;
        attribute :>> massKg = 35.19377680849091;
        attribute :>> evidenceAccepted = false;
        attribute :>> operatingMargins = (-0.0034497945894563786);
        attribute :>> structuralMargins = (0.95012551241916643,0.60697490766656381,0.70972900347325729,0.3250231564189493,0.91059709471054695,-0.25983237493429878,-0.36716555113396177,-0.23251048749892167,0.73795101563745258,0.045434182010065771,0.15230478798236058,0.63301191953702252,-0.015898106704652415,0.88432961195254223,2.190155342363703,1.3321889009175707,0.28054565813084908,1.1737992819589698,0.96795978558604012,0.92827778730948429,0.21400460169919389,0.68264105810567521);
        attribute :>> routeMargins = (3.0571961506550611,-0.5485729780448001,1,2.4514270219552001,0.057196150655061562,1);
        attribute :>> restoringMomentsNm = (20.562926296637674,22.766759478829695,20.563048977595543,22.712750472442298);
    }
    analysis constructionReview : BlueDogSizingEvidence::Review { subject :>> scenario = construction; }
    part aerodynamic : BlueDogSizingEvidence::Scenario {
        attribute :>> label = "aerodynamic";
        attribute limitingScreens : String = "keelDeflectionMargin: -1.271e-08; wingDeflectionMargin: -7.613e-09; operating/peak power: -1.56e-11";
        attribute easterlyDownstreamMps : Real = 2.0500996813609271;
        attribute easterlyUpstreamMps : Real = -0.0013020451514235143;
        attribute easterlyTimeLabel : String = if not numericallyBalanced or diagnosticControlCases > 0 ? "Diagnostic only" else if easterlyDownstreamMps <= 0 or easterlyUpstreamMps <= 0 ? "No completion (duration penalty)" else "1e+06";
        attribute westerlyDownstreamMps : Real = 1.4986979548485766;
        attribute westerlyUpstreamMps : Real = 0.55009968136092691;
        attribute westerlyTimeLabel : String = if not numericallyBalanced or diagnosticControlCases > 0 ? "Diagnostic only" else if westerlyDownstreamMps <= 0 or westerlyUpstreamMps <= 0 ? "No completion (duration penalty)" else "22.71";
        attribute :>> acceptanceRouteMargins = (1.9973959096971532,0.10019936272185381,1);
        attribute :>> numericallyBalanced = true;
        attribute :>> missingPitchRoots = 0;
        attribute :>> pitchUnstableSamples = 78;
        attribute :>> diagnosticControlCases = 0;
        attribute :>> easterlyHours = 1000000;
        attribute :>> westerlyHours = 22.706358340193432;
        attribute :>> massKg = 33.451612629662762;
        attribute :>> evidenceAccepted = false;
        attribute :>> operatingMargins = (-1.5596857139144049e-11);
        attribute :>> structuralMargins = (0.96232046666456039,0.68797127438754957,0.78768408845980287,0.47436189159818165,0.93246005802610732,-7.6129478276953932e-09,-1.2707505936404573e-08,0.040182656049085219,0.76297477341939546,0.018534601818054219,0.21518622194779502,0.64969800630459118,0.0041543100012498835,0.90085395310217908,2.2319079760072187,1.4536495912113572,0.2822853511993289,1.1737992819589698,0.9694571871275337,0.9321174247116053,0.30103041231927197,0.70697633910527957);
        attribute :>> routeMargins = (3.1001993627218543,-1.002604090302847,1,1.9973959096971532,0.10019936272185381,1);
        attribute :>> restoringMomentsNm = (20.461024795165429,22.56743407497024,20.461140176385193,22.516756516316924);
    }
    analysis aerodynamicReview : BlueDogSizingEvidence::Review { subject :>> scenario = aerodynamic; }
    part hydrodynamic : BlueDogSizingEvidence::Scenario {
        attribute :>> label = "hydrodynamic";
        attribute limitingScreens : String = "keelDeflectionMargin: -1.271e-08; wingDeflectionMargin: -7.613e-09; operating/peak power: -3.043e-11";
        attribute easterlyDownstreamMps : Real = 2.0334428096828874;
        attribute easterlyUpstreamMps : Real = 0.22652611415453172;
        attribute easterlyTimeLabel : String = if not numericallyBalanced or diagnosticControlCases > 0 ? "Diagnostic only" else if easterlyDownstreamMps <= 0 or easterlyUpstreamMps <= 0 ? "No completion (duration penalty)" else "44.83";
        attribute westerlyDownstreamMps : Real = 1.7265261141545318;
        attribute westerlyUpstreamMps : Real = 0.53344280968288738;
        attribute westerlyTimeLabel : String = if not numericallyBalanced or diagnosticControlCases > 0 ? "Diagnostic only" else if westerlyDownstreamMps <= 0 or westerlyUpstreamMps <= 0 ? "No completion (duration penalty)" else "22.42";
        attribute :>> acceptanceRouteMargins = (2.4530522283090637,0.066885619365774751,1);
        attribute :>> numericallyBalanced = true;
        attribute :>> missingPitchRoots = 0;
        attribute :>> pitchUnstableSamples = 78;
        attribute :>> diagnosticControlCases = 0;
        attribute :>> easterlyHours = 44.828701650274091;
        attribute :>> westerlyHours = 22.420504524115525;
        attribute :>> massKg = 33.451612629662762;
        attribute :>> evidenceAccepted = false;
        attribute :>> operatingMargins = (-3.0432767417210016e-11);
        attribute :>> structuralMargins = (0.96232046666456039,0.68797127438754957,0.78768408845980287,0.47436189159818165,0.93246005802610732,-7.6129478276953932e-09,-1.2707505936404573e-08,0.040182656049085219,0.76297477341939546,0.018534601818054219,0.21518622194779502,0.64969800630459118,0.0041543100012498835,0.90085395310217908,2.2319079760072187,1.4536495912113572,0.2822853511993289,1.1737992819589698,0.9694571871275337,0.9321174247116053,0.30103041231927197,0.70697633910527957);
        attribute :>> routeMargins = (3.0668856193657748,-0.54694777169093656,1,2.4530522283090637,0.066885619365774751,1);
        attribute :>> restoringMomentsNm = (20.461024795165429,22.56743407497024,20.461140176385193,22.516756516316924);
    }
    analysis hydrodynamicReview : BlueDogSizingEvidence::Review { subject :>> scenario = hydrodynamic; }
    part energy : BlueDogSizingEvidence::Scenario {
        attribute :>> label = "energy";
        attribute limitingScreens : String = "keelDeflectionMargin: -1.271e-08; wingDeflectionMargin: -7.613e-09; operating/peak power: -4.452e-13";
        attribute easterlyDownstreamMps : Real = 2.0648992805241333;
        attribute easterlyUpstreamMps : Real = 0.24861053884093698;
        attribute easterlyTimeLabel : String = if not numericallyBalanced or diagnosticControlCases > 0 ? "Diagnostic only" else if easterlyDownstreamMps <= 0 or easterlyUpstreamMps <= 0 ? "No completion (duration penalty)" else "41.18";
        attribute westerlyDownstreamMps : Real = 1.748610538840937;
        attribute westerlyUpstreamMps : Real = 0.5648992805241333;
        attribute westerlyTimeLabel : String = if not numericallyBalanced or diagnosticControlCases > 0 ? "Diagnostic only" else if westerlyDownstreamMps <= 0 or westerlyUpstreamMps <= 0 ? "No completion (duration penalty)" else "21.4";
        attribute :>> acceptanceRouteMargins = (2.497221077681874,0.12979856104826659,1);
        attribute :>> numericallyBalanced = true;
        attribute :>> missingPitchRoots = 0;
        attribute :>> pitchUnstableSamples = 78;
        attribute :>> diagnosticControlCases = 0;
        attribute :>> easterlyHours = 41.177205555190881;
        attribute :>> westerlyHours = 21.399871474949084;
        attribute :>> massKg = 33.451612629662762;
        attribute :>> evidenceAccepted = false;
        attribute :>> operatingMargins = (-4.4519943287468777e-13);
        attribute :>> structuralMargins = (0.96232046666456039,0.68797127438754957,0.78768408845980287,0.47436189159818165,0.93246005802610732,-7.6129478276953932e-09,-1.2707505936404573e-08,0.040182656049085219,0.76297477341939546,0.018534601818054219,0.21518622194779502,0.64969800630459118,0.0041543100012498835,0.90085395310217908,2.2319079760072187,1.4536495912113572,0.2822853511993289,1.1737992819589698,0.9694571871275337,0.9321174247116053,0.30103041231927197,0.70697633910527957);
        attribute :>> routeMargins = (3.1297985610482666,-0.50277892231812604,1,2.497221077681874,0.12979856104826659,1);
        attribute :>> restoringMomentsNm = (20.461024795165429,22.56743407497024,20.461140176385193,22.516756516316924);
    }
    analysis energyReview : BlueDogSizingEvidence::Review { subject :>> scenario = energy; }
    part combined : BlueDogSizingEvidence::Scenario {
        attribute :>> label = "combined";
        attribute limitingScreens : String = "westerly upstream progress: -0.6815; keelDeflectionMargin: -0.3672; wingDeflectionMargin: -0.2598";
        attribute easterlyDownstreamMps : Real = 2.1592714175795447;
        attribute easterlyUpstreamMps : Real = -0.34895710869965768;
        attribute easterlyTimeLabel : String = if not numericallyBalanced or diagnosticControlCases > 0 ? "Diagnostic only" else if easterlyDownstreamMps <= 0 or easterlyUpstreamMps <= 0 ? "No completion (duration penalty)" else "1e+06";
        attribute westerlyDownstreamMps : Real = 1.6510428913003423;
        attribute westerlyUpstreamMps : Real = 0.15927141757954466;
        attribute westerlyTimeLabel : String = if not numericallyBalanced or diagnosticControlCases > 0 ? "Diagnostic only" else if westerlyDownstreamMps <= 0 or westerlyUpstreamMps <= 0 ? "No completion (duration penalty)" else "62.9";
        attribute :>> acceptanceRouteMargins = (2.3020857826006846,-0.68145716484091068,1);
        attribute :>> numericallyBalanced = true;
        attribute :>> missingPitchRoots = 0;
        attribute :>> pitchUnstableSamples = 76;
        attribute :>> diagnosticControlCases = 8;
        attribute :>> easterlyHours = 1000000;
        attribute :>> westerlyHours = 62.901603115984216;
        attribute :>> massKg = 35.19377680849091;
        attribute :>> evidenceAccepted = false;
        attribute :>> operatingMargins = (-0.0034497945894563786);
        attribute :>> structuralMargins = (0.95012551241916643,0.60697490766656381,0.70972900347325729,0.3250231564189493,0.91059709471054695,-0.25983237493429878,-0.36716555113396177,-0.23251048749892167,0.73795101563745258,0.045434182010065771,0.15230478798236058,0.63301191953702252,-0.015898106704652415,0.88432961195254223,2.190155342363703,1.3321889009175707,0.28054565813084908,1.1737992819589698,0.96795978558604012,0.92827778730948429,0.21400460169919389,0.68264105810567521);
        attribute :>> routeMargins = (3.3185428351590893,-1.6979142173993154,1,2.3020857826006846,-0.68145716484091068,1);
        attribute :>> restoringMomentsNm = (20.562926296637674,22.766759478829695,20.563048977595543,22.712750472442298);
    }
    analysis combinedReview : BlueDogSizingEvidence::Review { subject :>> scenario = combined; }
    dependency candidateBasis from candidate to BlueDogDesignDecisions::sizingBaseline;
}
