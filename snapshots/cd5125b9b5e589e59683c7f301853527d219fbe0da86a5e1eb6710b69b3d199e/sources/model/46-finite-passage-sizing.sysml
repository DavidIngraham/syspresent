// Generated by tools.boat_analysis.evidence.continuation.
package BlueDogFinitePassageSizing {
    private import ScalarValues::*;
    doc /* Coarse fixed-length feasibility only; no refined replay or physical qualification.
     * Hull length does not bound the full vessel footprint. Appendage geometry/model applicability,
     * chronological voyage energy and free-pitch dynamic recovery require further assessment. */
    part summary {
        attribute targetM : Real = 1.3;
        attribute smallestFeasibleM : Real = 1.4;
        attribute targetReached : Boolean = false;
        attribute qualified : Boolean = false;
    }
    attribute evidenceManifest : String = "evidence/runs/2026-10-12-finite-passage/manifest.json";
    attribute stageNames : String [*] ordered nonunique = ("BlueDogFinitePassageSizing::stage0", "BlueDogFinitePassageSizing::stage1", "BlueDogFinitePassageSizing::stage2", "BlueDogFinitePassageSizing::stage3");
    part stage0 {
        attribute lengthM : Real = 2.0;
        attribute feasible : Boolean = true;
        attribute maximumResidual : Real = 4.182576190459031e-06;
        attribute minimumMargin : Real = -1.1025578690260218e-05;
        attribute massKg : Real = 34.52412299851067;
        attribute batteryWh : Real = 325.2078173450327;
        attribute sweptLengthM : Real = 2.055134910550832;
    }
    part stage1 {
        attribute lengthM : Real = 1.8;
        attribute feasible : Boolean = true;
        attribute maximumResidual : Real = 7.595253901313548e-05;
        attribute minimumMargin : Real = -1.2385637890588442e-05;
        attribute massKg : Real = 33.892094215193396;
        attribute batteryWh : Real = 336.57874745676276;
        attribute sweptLengthM : Real = 1.855512367580499;
    }
    part stage2 {
        attribute lengthM : Real = 1.6;
        attribute feasible : Boolean = true;
        attribute maximumResidual : Real = 1.282076064796911e-05;
        attribute minimumMargin : Real = -5.497405316079451e-05;
        attribute massKg : Real = 32.03456052626014;
        attribute batteryWh : Real = 339.4534569423761;
        attribute sweptLengthM : Real = 1.6560166270489536;
    }
    part stage3 {
        attribute lengthM : Real = 1.4;
        attribute feasible : Boolean = true;
        attribute maximumResidual : Real = 8.609802684258482e-05;
        attribute minimumMargin : Real = -3.352359621455747e-06;
        attribute massKg : Real = 29.88859101991109;
        attribute batteryWh : Real = 342.8229703130181;
        attribute sweptLengthM : Real = 1.4572906057700608;
    }
    part candidate : MarineDesign::Design {
        attribute :>> length_m = 1.4;
        attribute :>> beam_m = 0.5067999999997308;
        attribute :>> bottom_depth_m = 0.07825454337382551;
        attribute :>> deck_height_m = 0.07884291230310685;
        attribute :>> sail_m2 = 1.226228622011194;
        attribute :>> sail_AR = 2.257707673201315;
        attribute :>> camber_scale = 1.1269456057834304;
        attribute :>> wing_thickness_scale = 1.169694656497319;
        attribute :>> mast_fraction = 0.5162169792322526;
        attribute :>> mast_x_fraction = -0.02348623882263623;
        attribute :>> keel_m2 = 0.13506170600262693;
        attribute :>> keel_span_m = 0.663912474887663;
        attribute :>> rudder_m2 = 0.026262017317854536;
        attribute :>> rudder_span_m = 0.22920003170553543;
        attribute :>> rudder_arm_fraction = 0.5;
        attribute :>> ballast_kg = 12.052274648770574;
        attribute :>> battery_Wh = 342.8229703130181;
        attribute :>> panel_m2 = 0.2032306262224013;
        attribute :>> wing_torque_Nm = 3.492899663850968;
        attribute :>> rudder_torque_Nm = 0.7214713371678395;
        attribute :>> hull_glass_kg_m2 = 0.5154764183265355;
        attribute :>> wing_glass_kg_m2 = 0.2;
        attribute :>> keel_glass_kg_m2 = 4.781689503948721;
        attribute :>> rudder_glass_kg_m2 = 1.3034445787692075;
        attribute :>> hull_rib_pitch_m = 0.025559690195011968;
        attribute :>> foil_rib_pitch_m = 0.06512394400281599;
        attribute :>> battery_x_fraction = -0.3464999999999999;
        attribute :>> battery_z_fraction = 0.09316939078359278;
        attribute :>> hull_fullness_exponent = 1.8071152832027766;
    }
    dependency basis from candidate to BlueDogDesignDecisions::sizingBaseline;
    part assessment {
        attribute massKg : Real = 29.88859101991109;
        attribute westerlyHours : Real = 23.779129978035403;
        attribute rudderChordM : Real = candidate.rudder_m2 / candidate.rudder_span_m;
        attribute rudderAspectRatio : Real = candidate.rudder_span_m * candidate.rudder_span_m / candidate.rudder_m2;
        attribute neutralHullRudderLengthM : Real = NumericalFunctions::max(candidate.length_m/2, -candidate.rudder_arm_fraction*candidate.length_m + rudderChordM/2) + NumericalFunctions::max(candidate.length_m/2, candidate.rudder_arm_fraction*candidate.length_m + rudderChordM/2);
        attribute qualified : Boolean = false;
    }
    part passage {
        attribute voyageEnergyMargin : Real = -1.2150509149932985e-07;
        attribute installationVolumeMargin : Real = 1.9629070633050338;
        attribute passageHours : Real = 35.72391247254426;
        attribute departureWh : Real = 246.83253862537308;
        attribute requiredWh : Real = 246.83255077588223;
        attribute batteryVolumeM3 : Real = 0.0017141148515650907;
        attribute equipmentVolumeM3 : Real = 0.00832431130030564;
        attribute availableVolumeM3 : Real = 0.029667496784921074;
    }
    dependency energyBasis from passage to BlueDogConceptCredibility::passagePolicy;
    part validation {
        attribute recoverySamples : Real = 24;
        attribute missingPitchRoots : Real = 0;
        attribute unstablePitchSamples : Real = 8;
        attribute adverseRollSamples : Real = 0;
        attribute constructionWorstDeflectionMargin : Real = -0.42857621765660214;
    }
    dependency recoveryBasis from validation to BlueDogRequirements::selfRighting;
    part mission {
        attribute scenarios : Real = 4;
        attribute virtualCompletions : Real = 1;
        attribute coverageStops : Real = 3;
        attribute minimumStoredWh : Real = 178.69126064390255;
        attribute protectedReserveWh : Real = 49.2;
    }
    dependency missionBasis from mission to BlueDogMissionSimulation::MissionOutcome;
}
