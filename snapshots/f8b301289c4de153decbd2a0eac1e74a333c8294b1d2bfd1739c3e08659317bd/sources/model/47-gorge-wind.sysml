// Generated by tools.boat_analysis.environment.climatology from frozen NOAA observations.
package BlueDogWindObservations {
    private import ScalarValues::*;
    part KDLS_warm : BlueDogWeather::StationSeason {
        attribute :>> station = "KDLS";
        attribute :>> season = "warm";
        attribute :>> expectedHours = 36720;
        attribute :>> observedHours = 36673;
        attribute :>> westHours = 16550;
        attribute :>> eastHours = 1808;
        attribute :>> lightHours = 7237;
        attribute :>> otherHours = 10131;
        attribute :>> unknownHours = 994;
        attribute :>> selectedWindows = 1821;
        attribute :>> windowsWithEast = 782;
        attribute :>> incompleteWindows = 4394;
    }
    part KDLS_winter : BlueDogWeather::StationSeason {
        attribute :>> station = "KDLS";
        attribute :>> season = "winter";
        attribute :>> expectedHours = 36312;
        attribute :>> observedHours = 36257;
        attribute :>> westHours = 6281;
        attribute :>> eastHours = 5857;
        attribute :>> lightHours = 19082;
        attribute :>> otherHours = 4569;
        attribute :>> unknownHours = 523;
        attribute :>> selectedWindows = 488;
        attribute :>> windowsWithEast = 429;
        attribute :>> incompleteWindows = 856;
    }
    part KDLS_transition : BlueDogWeather::StationSeason {
        attribute :>> station = "KDLS";
        attribute :>> season = "transition";
        attribute :>> expectedHours = 14640;
        attribute :>> observedHours = 14506;
        attribute :>> westHours = 4600;
        attribute :>> eastHours = 1646;
        attribute :>> lightHours = 5634;
        attribute :>> otherHours = 2364;
        attribute :>> unknownHours = 396;
        attribute :>> selectedWindows = 455;
        attribute :>> windowsWithEast = 353;
        attribute :>> incompleteWindows = 1132;
    }
    part KDLS_annual : BlueDogWeather::StationSeason {
        attribute :>> station = "KDLS";
        attribute :>> season = "annual";
        attribute :>> expectedHours = 87672;
        attribute :>> observedHours = 87436;
        attribute :>> westHours = 27431;
        attribute :>> eastHours = 9311;
        attribute :>> lightHours = 31953;
        attribute :>> otherHours = 17064;
        attribute :>> unknownHours = 1913;
        attribute :>> selectedWindows = 2764;
        attribute :>> windowsWithEast = 1564;
        attribute :>> incompleteWindows = 6382;
    }
    part KTTD_warm : BlueDogWeather::StationSeason {
        attribute :>> station = "KTTD";
        attribute :>> season = "warm";
        attribute :>> expectedHours = 36720;
        attribute :>> observedHours = 36665;
        attribute :>> westHours = 5548;
        attribute :>> eastHours = 2481;
        attribute :>> lightHours = 19675;
        attribute :>> otherHours = 3575;
        attribute :>> unknownHours = 5441;
        attribute :>> selectedWindows = 0;
        attribute :>> windowsWithEast = 0;
        attribute :>> incompleteWindows = 61;
    }
    part KTTD_winter : BlueDogWeather::StationSeason {
        attribute :>> station = "KTTD";
        attribute :>> season = "winter";
        attribute :>> expectedHours = 36312;
        attribute :>> observedHours = 36264;
        attribute :>> westHours = 2788;
        attribute :>> eastHours = 17328;
        attribute :>> lightHours = 10909;
        attribute :>> otherHours = 4602;
        attribute :>> unknownHours = 685;
        attribute :>> selectedWindows = 44;
        attribute :>> windowsWithEast = 41;
        attribute :>> incompleteWindows = 110;
    }
    part KTTD_transition : BlueDogWeather::StationSeason {
        attribute :>> station = "KTTD";
        attribute :>> season = "transition";
        attribute :>> expectedHours = 14640;
        attribute :>> observedHours = 14557;
        attribute :>> westHours = 1741;
        attribute :>> eastHours = 3481;
        attribute :>> lightHours = 6669;
        attribute :>> otherHours = 1988;
        attribute :>> unknownHours = 761;
        attribute :>> selectedWindows = 1;
        attribute :>> windowsWithEast = 0;
        attribute :>> incompleteWindows = 55;
    }
    part KTTD_annual : BlueDogWeather::StationSeason {
        attribute :>> station = "KTTD";
        attribute :>> season = "annual";
        attribute :>> expectedHours = 87672;
        attribute :>> observedHours = 87486;
        attribute :>> westHours = 10077;
        attribute :>> eastHours = 23290;
        attribute :>> lightHours = 37253;
        attribute :>> otherHours = 10165;
        attribute :>> unknownHours = 6887;
        attribute :>> selectedWindows = 45;
        attribute :>> windowsWithEast = 41;
        attribute :>> incompleteWindows = 226;
    }
}
