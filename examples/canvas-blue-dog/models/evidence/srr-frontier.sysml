// Generated by tools.publishing.frontier; edit the source analysis, not these values.
package BlueDogSRRFrontier {
    private import ScalarValues::*;
    doc /* Local coarse monohull search, not physical qualification or a calibrated mission probability.
     * Unresolved searches do not prove infeasibility. The replay applies to the retained seed, not every alternative. */
    attribute evidenceManifest : String = "evidence/runs/2026-10-13-srr-frontier/manifest.json";
    attribute pointNames : String [*] ordered nonunique = ("BlueDogSRRFrontier::point0", "BlueDogSRRFrontier::point1", "BlueDogSRRFrontier::point2", "BlueDogSRRFrontier::point3", "BlueDogSRRFrontier::point4", "BlueDogSRRFrontier::point5");
    part point0 {
        attribute capM : Real = 1.2;
        attribute optimizationObjective : String = "massKg";
        attribute feasible : Boolean = true;
        attribute solverConverged : Boolean = false;
        attribute overallLengthM : Real = 1.19999999999918;
        attribute massKg : Real = 10.251979623823363;
        attribute conditionalPassageHours : Real = 33.69993514266723;
        attribute maxEquilibriumResidual : Real = 3.0056176298520753e-05;
        attribute minimumMargin : Real = -2.8849930515093548e-05;
    }
    part point1 {
        attribute capM : Real = 1.2;
        attribute optimizationObjective : String = "conditionalPassageHours";
        attribute feasible : Boolean = true;
        attribute solverConverged : Boolean = false;
        attribute overallLengthM : Real = 1.19999999999912;
        attribute massKg : Real = 10.252018537728546;
        attribute conditionalPassageHours : Real = 33.660701261300844;
        attribute maxEquilibriumResidual : Real = 3.455479958631713e-05;
        attribute minimumMargin : Real = -3.05103158257225e-05;
    }
    part point2 {
        attribute capM : Real = 1.0;
        attribute optimizationObjective : String = "massKg";
        attribute feasible : Boolean = false;
        attribute solverConverged : Boolean = false;
        attribute overallLengthM : Real = 0.99999999999978;
        attribute massKg : Real = 10.552607614662792;
        attribute conditionalPassageHours : Real = 39.54397530339136;
        attribute maxEquilibriumResidual : Real = 0.013272813945328643;
        attribute minimumMargin : Real = -0.07408293173826053;
    }
    part point3 {
        attribute capM : Real = 1.0;
        attribute optimizationObjective : String = "conditionalPassageHours";
        attribute feasible : Boolean = false;
        attribute solverConverged : Boolean = false;
        attribute overallLengthM : Real = 1.08287401940678;
        attribute massKg : Real = 13.915531549193123;
        attribute conditionalPassageHours : Real = 29.093649494420255;
        attribute maxEquilibriumResidual : Real = 0.06851245536571367;
        attribute minimumMargin : Real = -0.3060228212366165;
    }
    part point4 {
        attribute capM : Real = 0.8;
        attribute optimizationObjective : String = "massKg";
        attribute feasible : Boolean = false;
        attribute solverConverged : Boolean = false;
        attribute overallLengthM : Real = 0.93547442072642;
        attribute massKg : Real = 11.359587063925092;
        attribute conditionalPassageHours : Real = 52.414615902711915;
        attribute maxEquilibriumResidual : Real = 0.14332133293069468;
        attribute minimumMargin : Real = -0.559342149485484;
    }
    part point5 {
        attribute capM : Real = 0.8;
        attribute optimizationObjective : String = "conditionalPassageHours";
        attribute feasible : Boolean = false;
        attribute solverConverged : Boolean = false;
        attribute overallLengthM : Real = 0.91345640313512;
        attribute massKg : Real = 10.91774017210988;
        attribute conditionalPassageHours : Real = 45.921314701972314;
        attribute maxEquilibriumResidual : Real = 0.09582011825541861;
        attribute minimumMargin : Real = -0.4289869070673995;
    }
    part retainedSeedReplay {
        attribute massKg : Real = 10.252018537728546;
        attribute westerlyHours : Real = 33.74174149441574;
        attribute numericallyBalanced : Boolean = true;
        attribute voyageEnergyMargin : Real = -0.0055600033951458275;
        attribute sampledRightingPass : Boolean = true;
        attribute profileScreensPass : Boolean = false;
        attribute qualified : Boolean = false;
    }
}
